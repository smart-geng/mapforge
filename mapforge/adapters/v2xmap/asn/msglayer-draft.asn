-- 消息层数据集 ASN.1（自动提取自《基于LTE的车联网无线通信技术 消息层技术要求》送审稿 docx）
-- 提取工具：scripts/m0_extract_asn.py；人工校对状态见 out/asn_extract_report.md
-- 注意：送审稿文本，发布级交付前须与正式版 YD/T 3709-2020 做差异核对
MsgLayerDraft DEFINITIONS AUTOMATIC TAGS ::= BEGIN
 -- Main message frame

 MessageFrame ::= CHOICE {

 bsmFrame BasicSafetyMessage,

 mapFrame MapData,

 rsmFrame RoadsideSafetyMessage,

 spatFrame SPAT,

 rsiFrame RoadSideInformation,

 ...

 }

 BasicSafetyMessage ::= SEQUENCE {

 msgCnt MsgCount,

 id OCTET STRING (SIZE(8)),

 -- temperary vehicle ID

 secMark DSecond,

 timeConfidence TimeConfidence OPTIONAL,

 pos Position3D,

 posAccuracy PositionalAccuracy OPTIONAL,

 -- Accuracy for GNSS system

 posConfidence PositionConfidenceSet OPTIONAL,

 -- Realtime position confidence

 transmission TransmissionState,

 speed Speed,

 heading Heading,

 angle SteeringWheelAngle OPTIONAL,

 motionCfd MotionConfidenceSet OPTIONAL,

 accelSet AccelerationSet4Way,

 brakes BrakeSystemStatus,

 size VehicleSize,

 vehicleClass VehicleClassification,

 -- VehicleClassification includes BasicVehicleClass and other extendible type

 safetyExt VehicleSafetyExtensions OPTIONAL,

 emergencyExt VehicleEmergencyExtensions OPTIONAL,

 ...

 }

 MapData ::= SEQUENCE {

 msgCnt MsgCount,

 timeStamp MinuteOfTheYear OPTIONAL,

 nodes NodeList,

 -- intersections or road endpoints

 ...

 }

 RoadSideInformation ::= SEQUENCE {

 msgCnt MsgCount,

 moy MinuteOfTheYear OPTIONAL,

 id OCTET STRING (SIZE(8)),

 -- RSU ID

 refPos Position3D,

 -- Reference position of this RSI message

 rtes RTEList OPTIONAL,

 -- All the rte data packed in this message

 rtss RTSList OPTIONAL,

 -- All the rts data packed in this message

 ...

 }

 RoadsideSafetyMessage ::= SEQUENCE {

 msgCnt MsgCount,

 id OCTET STRING (SIZE(8)),

 -- RSU ID

 refPos Position3D,

 -- Reference position of this RSM message

 participants ParticipantList,

 -- All or part of the participants

 -- detected by RSU

 ...

 }

 SPAT ::= SEQUENCE {

 msgCnt MsgCount,

 moy MinuteOfTheYear OPTIONAL,

 timeStamp DSecond OPTIONAL,

 -- Time stamp when this message is formed

 name DescriptiveName OPTIONAL,

 -- human readable name for this collection

 -- to be used only in debug mode

 intersections IntersectionStateList,

 -- sets of SPAT data (one per intersection)

 ...

 }

 AccelerationSet4Way ::= SEQUENCE {

 long Acceleration,

 -- Along the Vehicle Longitudinal axis

 lat Acceleration,

 -- Along the Vehicle Lateral axis

 vert VerticalAcceleration,

 -- Along the Vehicle Vertical axis

 yaw YawRate

 }

 BrakeSystemStatus ::= SEQUENCE {

 brakePadel BrakePedalStatus OPTIONAL,

 wheelBrakes BrakeAppliedStatus OPTIONAL,

 traction TractionControlStatus OPTIONAL,

 abs AntiLockBrakeStatus OPTIONAL,

 scs StabilityControlStatus OPTIONAL,

 brakeBoost BrakeBoostApplied OPTIONAL,

 auxBrakes AuxiliaryBrakeStatus OPTIONAL

 }

 ConnectingLane ::= SEQUENCE {

 lane LaneID,

 -- Index of the connecting lane

 maneuver AllowedManeuvers OPTIONAL

 -- The Maneuver between

 -- the enclosing lane and this lane

 -- at the stop line to connect them

 }

 Connection::= SEQUENCE {

 remoteIntersection NodeReferenceID,

 -- This entry indicates the downstream intersection of the link this lane connects to.

 -- This provides a means to create meshes of lanes

 connectingLane ConnectingLane OPTIONAL,

 -- The index of the connecting lane and also

 -- the maneuver from the current lane to it

 -- When we want to list the allowed lanes of the next link

 -- this lane can lead to, we use this entry

 phaseId PhaseID OPTIONAL

 -- The matching signal group send by

 -- the SPAT message for this lane/maneuver.

 -- Shall be present unless the connectingLane

 -- has no signal group (is un-signalized)

 }

ConnectsToList ::= SEQUENCE (SIZE(1..8)) OF Connection

 DDateTime ::= SEQUENCE {

 year DYear OPTIONAL,

 month DMonth OPTIONAL,

 day DDay OPTIONAL,

 hour DHour OPTIONAL,

 minute DMinute OPTIONAL,

 second DSecond OPTIONAL,

 offset DTimeOffset OPTIONAL -- time zone

 }

 Description ::= CHOICE{

 textString IA5String (SIZE(1..512)),

 -- ASCII text

 textGB2312 OCTET STRING (SIZE(2..512))

 -- text using Chinese-character encoding GB2312-80

 }

 FullPositionVector ::= SEQUENCE {

 utcTime DDateTime OPTIONAL, -- time with mSec precision

 pos Position3D,

 heading Heading OPTIONAL,

 transmission TransmissionState OPTIONAL,

 speed Speed OPTIONAL,

 posAccuracy PositionConfidenceSet OPTIONAL,

 timeConfidence TimeConfidence OPTIONAL,

 motionCfd MotionConfidenceSet OPTIONAL,

 ...

 }

 IntersectionState ::= SEQUENCE {

 intersectionId NodeReferenceID,

 -- A globally unique value set, consisting of a

 -- regionID and intersection ID assignment

 -- provides a unique mapping to the MAP Node

 status IntersectionStatusObject,

 -- general status of the controller(s)

 moy MinuteOfTheYear OPTIONAL,

 -- Minute of current UTC year

 -- used only with messages to be archived

 timeStamp DSecond OPTIONAL,

 -- the mSec point in the current UTC minute that

 -- this message was constructed

 timeConfidence TimeConfidence OPTIONAL,

 -- indicate the time confidence of the above UTC time

 phases PhaseList

 -- Each Movement is given in turn

 -- and contains its signal phase state

 -- mapping to the lanes it applies to, and

 -- point in time it will end, and it

 -- may contain both active and future states

 }

IntersectionStateList ::= SEQUENCE (SIZE(1..32)) OF IntersectionState

 Lane ::= SEQUENCE {

 laneID LaneID,

 -- The unique ID number assigned

 -- to this lane object

 laneWidth LaneWidth OPTIONAL,

 laneAttributes LaneAttributes OPTIONAL,

 -- Define basic attribute of lane

 maneuvers AllowedManeuvers OPTIONAL,

 -- the permitted maneuvers for this lane

 connectsTo ConnectsToList OPTIONAL,

 -- connection to downsteam lanes

 speedLimits SpeedLimitList OPTIONAL,

 -- List all the speed limits

 points PointList OPTIONAL,

 -- Define road points and segments

 ...

 }

 LaneAttributes ::= SEQUENCE {

 shareWith LaneSharing OPTIONAL,

 laneType LaneTypeAttributes

 }

LaneList ::= SEQUENCE (SIZE(1..32)) OF Lane

 LaneTypeAttributes ::= CHOICE {

 vehicle LaneAttributes-Vehicle, -- motor vehicle lanes

 crosswalk LaneAttributes-Crosswalk, -- pedestrian crosswalks

 bikeLane LaneAttributes-Bike, -- bike lanes

 sidewalk LaneAttributes-Sidewalk, -- pedestrian sidewalk paths

 median LaneAttributes-Barrier, -- medians & channelization

 striping LaneAttributes-Striping, -- roadway markings

 trackedVehicle LaneAttributes-TrackedVehicle, -- trains and trolleys

 parking LaneAttributes-Parking, -- parking and stopping lanes

 ...

 }

 Link ::= SEQUENCE {

 name DescriptiveName OPTIONAL,

 -- Link name

 upstreamNodeId NodeReferenceID,

 -- this link is from upstreamNode to the Node it belongs to

 speedLimits SpeedLimitList OPTIONAL,

 -- List all the speed limits

 linkWidth LaneWidth,

 -- Width of this link

 points PointList OPTIONAL,

 -- Define road points along the center of this link

 movements MovementList OPTIONAL,

 -- Define movements at intersection

 lanes LaneList,

 -- Lanes belong to this link

 ...

 }

LinkList ::= SEQUENCE (SIZE(1..32)) OF Link

 MotionConfidenceSet ::= SEQUENCE {

 speedCfd SpeedConfidence OPTIONAL,

 headingCfd HeadingConfidence OPTIONAL,

 steerCfd SteeringWheelAngleConfidence OPTIONAL

 }

 Movement ::= SEQUENCE {

 remoteIntersection NodeReferenceID,

 -- This entry indicates the downstream intersection of the link this lane connects to.

 -- This provides a means to create meshes of lanes

 phaseId PhaseID OPTIONAL

 -- The matching signal group send by

 -- the SPAT message for this lane/maneuver.

 -- Shall be present unless the connectingLane

 -- has no signal group (is un-signalized)

 }

MovementList ::= SEQUENCE (SIZE(1..32)) OF Movement

 Node ::= SEQUENCE {

 -- Node can be an intersection, or a road endpoint

 name DescriptiveName OPTIONAL,

 -- Node name

 id NodeReferenceID,

 -- A globally unique value set,

 -- consisting of a regionID and

 -- node ID assignment

 refPos Position3D,

 -- 3D position of the center of this Node.

 -- This position is also the reference position for the elements inside

 inLinks LinkList OPTIONAL,

 -- all the links enter this Node

 ...

 }

NodeList ::= SEQUENCE (SIZE(1..32)) OF Node

 NodeReferenceID ::= SEQUENCE {

 region RoadRegulatorID OPTIONAL,

 -- a globally unique regional assignment value

 -- typical assigned to a regional DOT authority

 -- the value zero shall be used for testing needs

 id NodeID

 -- a unique mapping to the node

 -- in question within the above region of use

 }

 ParticipantData ::= SEQUENCE {

 ptcType ParticipantType,

 ptcId INTEGER (0..65535),

 -- temporary ID set by RSU

 -- 0 is RSU itself

 -- 1..255 represent participants detected by RSU

 -- ptcId of different participant needs to be unique in RSU

 source SourceType,

 id OCTET STRING (SIZE(8)) OPTIONAL,

 -- temperary vehicle ID from BSM

 secMark DSecond,

 pos PositionOffsetLLV,

 posConfidence PositionConfidenceSet,

 transmission TransmissionState OPTIONAL,

 speed Speed,

 heading Heading,

 angle SteeringWheelAngle OPTIONAL,

 motionCfd MotionConfidenceSet OPTIONAL,

 accelSet AccelerationSet4Way OPTIONAL,

 size VehicleSize,

 -- Size of participant including motor/non-motor/pedestrian/rsu

 -- is represented by DE_VehilceSize

 vehicleClass VehicleClassification OPTIONAL,

 ...

 }

ParticipantList ::= SEQUENCE (SIZE(1..16)) OF ParticipantData

 PathHistory ::= SEQUENCE {

 initialPosition FullPositionVector OPTIONAL,

 currGNSSstatus GNSSstatus OPTIONAL,

 crumbData PathHistoryPointList,

 ...

 }

 PathHistoryPoint ::= SEQUENCE {

 llvOffset PositionOffsetLLV,

 timeOffset TimeOffset,

 -- Offset backwards in time

 speed Speed OPTIONAL,

 -- Speed over the reported period

 posAccuracy PositionConfidenceSet OPTIONAL,

 -- The accuracy of this value

 heading CoarseHeading OPTIONAL,

 -- overall heading

 ...

 }

PathHistoryPointList ::= SEQUENCE (SIZE(1..23)) OF PathHistoryPoint

 PathPointList ::= SEQUENCE (SIZE(2..32)) OF PositionOffsetLLV

 -- Path point list for RTS message

 PathPrediction ::= SEQUENCE {

 radiusOfCurve RadiusOfCurvature,

 -- Units of 10cm

 -- straight path to use value of 32767

 confidence Confidence,

 -- Units of 0.5 percent

 ...

 }

 Phase ::= SEQUENCE{

 id PhaseID,

 -- the group id is used to map to lists

 -- of lanes (and their descriptions)

 -- which this MovementState data applies to

 -- see comments in the Remarks for usage details

 phaseStates PhaseStateList

 -- Consisting of sets of movement data with:

 -- a) SignalPhaseState

 -- b) TimeChangeDetails, and

 -- c) AdvisorySpeeds (optional )

 -- Note one or more of the movement events may be for

 -- a future time and that this allows conveying multiple

 -- predictive phase and movement timing for various uses

 -- for the current signal group

 }

 PhaseList ::= SEQUENCE (SIZE(1..16)) OF Phase

 -- List of phases in one traffic signal

 PhaseState ::= SEQUENCE {

 light LightState,

 -- Consisting of:

 -- Phase state (the basic 11 states)

 -- Directional, protected, or permissive state

 timing TimeChangeDetails OPTIONAL,

 -- Timing Data in UTC time stamps for event

 -- includes start and min/max end times of phase

 -- confidence and estimated next occurrence

 ...

 }

PhaseStateList ::= SEQUENCE (SIZE(1..16)) OF PhaseState

 PointList ::= SEQUENCE (SIZE(2..31)) OF RoadPoint

 -- At least 2 points of 1 lane

 -- entry line and exit line

 -- points need to be listed sequentially

 -- from upstream to downstream

 Position-LL-24B ::= SEQUENCE {

 -- ranges of +- 0.0002047 degrees

 -- ranges of +- 22.634554 meters at the equator

 lon OffsetLL-B12,

 lat OffsetLL-B12

 }

 Position-LL-28B ::= SEQUENCE {

 -- ranges of +- 0.0008191 degrees

 -- ranges of +- 90.571389 meters at the equator

 lon OffsetLL-B14,

 lat OffsetLL-B14

 }

 Position-LL-32B ::= SEQUENCE {

 -- ranges of +- 0.0032767 degrees

 -- ranges of +- 362.31873 meters at the equator

 lon OffsetLL-B16,

 lat OffsetLL-B16

 }

 Position-LL-36B ::= SEQUENCE {

 -- ranges of +- 0.0131071 degrees

 -- ranges of +- 01.449308 Kmeters at the equator

 lon OffsetLL-B18,

 lat OffsetLL-B18

 }

 Position-LL-44B ::= SEQUENCE {

 -- ranges of +- 0.2097151 degrees

 -- ranges of +- 23.189096 Kmeters at the equator

 lon OffsetLL-B22,

 lat OffsetLL-B22

 }

 Position-LL-48B ::= SEQUENCE {

 -- ranges of +- 0.8388607 degrees

 -- ranges of +- 92.756481 Kmeters at the equator

 lon OffsetLL-B24,

 lat OffsetLL-B24

 }

 Position-LLmD-64b ::= SEQUENCE {

 -- a full 32b Lat/Lon range

 lon Longitude,

 lat Latitude

 }

 Position3D ::= SEQUENCE {

 lat Latitude,

 -- in 1/10th micro degrees

 long Longitude,

 -- in 1/10th micro degrees

 elevation Elevation OPTIONAL

 -- in 10 cm units

 }

 PositionalAccuracy ::= SEQUENCE {

 -- NMEA-183 values expressed in strict ASN form

 semiMajor SemiMajorAxisAccuracy,

 semiMinor SemiMinorAxisAccuracy,

 orientation SemiMajorAxisOrientation

 }

 PositionConfidenceSet ::= SEQUENCE {

 pos PositionConfidence, -- for both horizontal directions

 elevation ElevationConfidence OPTIONAL

 }

 PositionOffsetLL ::= CHOICE {

 -- Locations with LL content Span at the equator when using a zoom of one:

 position-LL1 Position-LL-24B,

 -- within +- 22.634554 meters of the reference position

 position-LL2 Position-LL-28B,

 -- within +- 90.571389 meters of the reference position

 position-LL3 Position-LL-32B,

 -- within +- 362.31873 meters of the reference position

 position-LL4 Position-LL-36B,

 -- within +- 01.449308 Kmeters of the reference position

 position-LL5 Position-LL-44B,

 -- within +- 23.189096 Kmeters of the reference position

 position-LL6 Position-LL-48B,

 -- within +- 92.756481 Kmeters of the reference position

 position-LatLon Position-LLmD-64b

 -- node is a Lat/Lon absolute coordinates

 -- not a reference position

 }

 PositionOffsetLLV ::= SEQUENCE {

 offsetLL PositionOffsetLL,

 -- offset in lon/lat

 offsetV VerticalOffset OPTIONAL

 -- offset in elevation

 }

 ReferenceLink ::= SEQUENCE {

 -- this Link is from Node of upstreamNodeId to Node of downstreamNodeId

 upstreamNodeId NodeReferenceID,

 downstreamNodeId NodeReferenceID,

 referenceLanes ReferenceLanes OPTIONAL

 -- Provide reference lanes if is necessary

 -- Refer to all lanes if this data is not given

 }

ReferenceLinkList ::= SEQUENCE (SIZE(1..16)) OF ReferenceLink

 ReferencePath ::= SEQUENCE {

 activePath PathPointList,

 -- RSI is active for vehicles within this path

 -- Points are listed from upstream to downstream

 -- along the vehicle drive direction.

 -- One path includes at least 1 points.

 -- A path with only 1 point means a round alert area

 pathRadius Radius

 -- The biggest distance away from the alert path

 -- within which the warning is active.

 }

ReferencePathList ::= SEQUENCE (SIZE(1..8)) OF ReferencePath

 RegulatorySpeedLimit ::= SEQUENCE {

 type SpeedLimitType,

 -- The type of regulatory speed which follows

 speed Speed

 -- The speed in units of 0.02 m/s

 -- See Section 11 for converting and translating

 -- speed expressed in mph into units of m/s

 }

 RSITimeDetails ::= SEQUENCE {

 startTime MinuteOfTheYear OPTIONAL,

 endTime MinuteOfTheYear OPTIONAL,

 -- Exact or estimated end time

 endTimeConfidence TimeConfidence OPTIONAL

 }

 RTEData ::= SEQUENCE {

 rteId INTEGER (0..255),

 -- local ID of this rte information set by RSU

 eventType EventType,

 -- Type of event, according to China GB/T 29100-2012

 eventSource EventSource,

 eventPos PositionOffsetLLV OPTIONAL,

 -- Position of this event, if exists

 eventRadius Radius OPTIONAL,

 -- Radius of this event, if exists

 description Description OPTIONAL,

 -- Additional description to this event

 timeDetails RSITimeDetails OPTIONAL,

 -- Start time or end time when this event is active

 priority RSIPriority OPTIONAL,

 -- the urgency of this RSI data, a relative

 -- degree of merit compared with other RSI data

 referencePaths ReferencePathList OPTIONAL,

 -- Related paths of this traffic event

 referenceLinks ReferenceLinkList OPTIONAL,

 -- Related links of this traffic event

 eventConfidence Confidence OPTIONAL,

 -- indicate the event confidence set by event source

 -- the probability/confidence of the detected event

 -- being truly extent at a certain place,

 -- to help vehicle determine whether to trust the received information.

 ...

 }

 RTEList ::= SEQUENCE (SIZE(1..8)) OF RTEData

 -- Road Traffic Event List

 RTSData ::= SEQUENCE {

 rtsId INTEGER (0..255),

 -- local ID of this rts information set by RSU

 signType SignType,

 -- Type of sign, according to China GB 5768.2-2009

 signPos PositionOffsetLLV OPTIONAL,

 -- Position of the traffic sign, if exists

 description Description OPTIONAL,

 -- Additional description to the sign

 timeDetails RSITimeDetails OPTIONAL,

 -- start time or end time when this sign is active, if existed

 priority RSIPriority OPTIONAL,

 -- the urgency of this RSI data, a relative

 -- degree of merit compared with other RSI data

 referencePaths ReferencePathList OPTIONAL,

 -- Related paths of this traffic sign

 referenceLinks ReferenceLinkList OPTIONAL,

 -- Related links of this traffic sign

 ...

 }

RTSList ::= SEQUENCE (SIZE(1..16)) OF RTSData

 RoadPoint ::= SEQUENCE {

 posOffset PositionOffsetLLV,

 -- Position offset to the reference position

 ...

 }

 SignalState ::= SEQUENCE {

 status IntersectionStatusObject,

 -- general status of the controller(s)

 moy MinuteOfTheYear OPTIONAL,

 -- Minute of current UTC year

 -- used only with messages to be archived

 timeStamp DSecond OPTIONAL,

 -- the mSec point in the current UTC minute that

 -- this message was constructed

 phases PhaseList

 -- Each Movement is given in turn

 -- and contains its signal phase state

 -- mapping to the lanes it applies to, and

 -- point in time it will end, and it

 -- may contain both active and future states

 }

SpeedLimitList ::= SEQUENCE (SIZE(1..9)) OF RegulatorySpeedLimit

 TimeChangeDetails ::= CHOICE {

 counting TimeCountingDown,

 utcTiming UTCTiming,

 ...

 }

 TimeCountingDown ::= SEQUENCE {

 startTime TimeMark,

 -- When this phase state started,

 -- if already started, the value is 0

 minEndTime TimeMark OPTIONAL,

 -- Expected shortest end time

 -- the value is the min left time from now

 maxEndTime TimeMark OPTIONAL,

 -- Expected longest end time

 -- the value is the max left time from now

 likelyEndTime TimeMark,

 -- Best predicted value based on other data

 -- the value is the likely left time from now

 timeConfidence Confidence OPTIONAL,

 -- Confidence of likelyTime

 nextStartTime TimeMark OPTIONAL,

 -- A rough estimate of time from now when this phase state may next occur again

 -- used to support various ECO driving power management needs.

 -- If already started, this value is recommended to be delivered.

 nextDuration TimeMark OPTIONAL

 -- A rough estimate of the time length of this phase state

 -- when it may next occur again.

 -- used to support various ECO driving power management needs.

 -- If already started, this value is recommended to be delivered.

 }

 UTCTiming ::= SEQUENCE {

 startUTCTime TimeMark,

 -- If already started, the value represents

 -- the time stamp when this phase state started.

 -- If not, the value represents

 -- the time stamp when this phase state starts.

 minEndUTCTime TimeMark OPTIONAL,

 -- The time stamp when this state 1st ends in shortest time

 maxEndUTCTime TimeMark OPTIONAL,

 -- The time stamp when this state 1st ends in longest time

 likelyEndUTCTime TimeMark,

 -- The time stamp when this state 1st ends in best predicted time

 timeConfidence Confidence OPTIONAL,

 -- Confidence of likelyEndUTCTime

 nextStartUTCTime TimeMark OPTIONAL,

 -- A rough estimate of UTC time stamp when this phase state may next occur again

 -- used to support various ECO driving power management needs.

 -- If already started, this value is recommended to be delivered.

 nextEndUTCTime TimeMark OPTIONAL

 -- A rough estimate of UTC time stamp when this phase state ends again

 -- used to support various ECO driving power management needs.

 -- If already started, this value is recommended to be delivered.

 }

 VehicleClassification ::= SEQUENCE {

 classification BasicVehicleClass,

 fuelType FuelType OPTIONAL,

 ...

 }

 VehicleEmergencyExtensions ::= SEQUENCE {

 responseType ResponseType OPTIONAL,

 sirenUse SirenInUse OPTIONAL,

 lightsUse LightbarInUse OPTIONAL,

 ...

 }

 VehicleSafetyExtensions ::= SEQUENCE {

 events VehicleEventFlags OPTIONAL,

 pathHistory PathHistory OPTIONAL,

 pathPrediction PathPrediction OPTIONAL,

 lights ExteriorLights OPTIONAL,

 ...

 }

 VehicleSize ::= SEQUENCE {

 width VehicleWidth,

 length VehicleLength,

 height VehicleHeight OPTIONAL

 }

 VerticalOffset ::= CHOICE {

 -- Vertical Offset

 -- All below in steps of 10cm above or below the reference ellipsoid

 offset1 VertOffset-B07, -- with a range of +- 6.3 meters vertical

 offset2 VertOffset-B08, -- with a range of +- 12.7 meters vertical

 offset3 VertOffset-B09, -- with a range of +- 25.5 meters vertical

 offset4 VertOffset-B10, -- with a range of +- 51.1 meters vertical

 offset5 VertOffset-B11, -- with a range of +- 102.3 meters vertical

 offset6 VertOffset-B12, -- with a range of +- 204.7 meters vertical

 elevation Elevation -- with a range of -409.5 to + 6143.9 meters

 }

 Acceleration ::= INTEGER (-2000..2001)

 -- Units of 0.01 m/s\^2

 -- the value 2000 shall be used for values greater than 2000

 -- the value -2000 shall be used for values less than -2000

 -- a value of 2001 shall be used for Unavailable

 AllowedManeuvers ::= BIT STRING {

 -- With bits as defined:

 -- Allowed maneuvers at path end (stop line)

 -- All maneuvers with bits not set are therefore prohibited

 -- A value of zero shall be used for unknown, indicating no Maneuver

 maneuverStraightAllowed (0),

 -- a Straight movement is allowed in this lane

 maneuverLeftAllowed (1),

 -- a Left Turn movement is allowed in this lane

 maneuverRightAllowed (2),

 -- a Right Turn movement is allowed in this lane

 maneuverUTurnAllowed (3),

 -- a U turn movement is allowed in this lane

 maneuverLeftTurnOnRedAllowed (4),

 -- a Stop, and then proceed when safe movement

 -- is allowed in this lane

 maneuverRightTurnOnRedAllowed (5),

 -- a Stop, and then proceed when safe movement

 -- is allowed in this lane

 maneuverLaneChangeAllowed (6),

 -- a movement which changes to an outer lane

 -- on the egress side is allowed in this lane

 -- (example: left into either outbound lane)

 maneuverNoStoppingAllowed (7),

 -- the vehicle should not stop at the stop line

 -- (example: a flashing green arrow)

 yieldAllwaysRequired (8),

 -- the allowed movements above are not protected

 -- (example: an permanent yellow condition)

 goWithHalt (9),

 -- after making a full stop, may proceed

 caution (10),

 -- proceed past stop line with caution

 reserved1 (11)

 -- used to align to 12 Bit Field

 } (SIZE(12))

 AntiLockBrakeStatus ::= ENUMERATED {

 unavailable (0), -- Vehicle Not Equipped with ABS Brakes

 -- or ABS Brakes status is unavailable

 off (1), -- Vehicle's ABS are Off

 on (2), -- Vehicle's ABS are On ( but not Engaged )

 engaged (3) -- Vehicle's ABS control is Engaged on any wheel

 }

 AuxiliaryBrakeStatus ::= ENUMERATED {

 unavailable (0), -- Vehicle Not Equipped with Aux Brakes

 -- or Aux Brakes status is unavailable

 off (1), -- Vehicle's Aux Brakes are Off

 on (2), -- Vehicle's Aux Brakes are On ( Engaged )

 reserved (3)

 }

 BasicVehicleClass ::= INTEGER (0..255)

 unknownVehicleClass BasicVehicleClass ::= 0

 -- Not Equipped, Not known or unavailable

 specialVehicleClass BasicVehicleClass ::= 1

 -- Special use

 --

 -- Basic Passenger Motor Vehicle Types

 --

 passenger-Vehicle-TypeUnknown BasicVehicleClass ::= 10 -- default type

 passenger-Vehicle-TypeOther BasicVehicleClass ::= 11

 -- various fuel types are handled in another element

 --

 -- Light Trucks, Pickup, Van, Panel

 --

 lightTruck-Vehicle-TypeUnknown BasicVehicleClass ::= 20 -- default type

 lightTruck-Vehicle-TypeOther BasicVehicleClass ::= 21

 --

 -- Trucks, Various axle types, includes HPMS items

 --

 truck-Vehicle-TypeUnknown BasicVehicleClass ::= 25 -- default type

 truck-Vehicle-TypeOther BasicVehicleClass ::= 26

 truck-axleCnt2 BasicVehicleClass ::= 27 -- Two axle, six tire single units

 truck-axleCnt3 BasicVehicleClass ::= 28 -- Three axle, single units

 truck-axleCnt4 BasicVehicleClass ::= 29 -- Four or more axle, single unit

 truck-axleCnt4Trailer BasicVehicleClass ::= 30 -- Four or less axle, single trailer

 truck-axleCnt5Trailer BasicVehicleClass ::= 31 -- Five or less axle, single trailer

 truck-axleCnt6Trailer BasicVehicleClass ::= 32 -- Six or more axle, single trailer

 truck-axleCnt5MultiTrailer BasicVehicleClass ::= 33 -- Five or less axle, multi-trailer

 truck-axleCnt6MultiTrailer BasicVehicleClass ::= 34 -- Six axle, multi-trailer

 truck-axleCnt7MultiTrailer BasicVehicleClass ::= 35 -- Seven or more axle, multi-trailer

 --

 -- Motorcycle Types

 --

 motorcycle-TypeUnknown BasicVehicleClass ::= 40 -- default type

 motorcycle-TypeOther BasicVehicleClass ::= 41

 motorcycle-Cruiser-Standard BasicVehicleClass ::= 42

 motorcycle-SportUnclad BasicVehicleClass ::= 43

 motorcycle-SportTouring BasicVehicleClass ::= 44

 motorcycle-SuperSport BasicVehicleClass ::= 45

 motorcycle-Touring BasicVehicleClass ::= 46

 motorcycle-Trike BasicVehicleClass ::= 47

 motorcycle-wPassengers BasicVehicleClass ::= 48 -- type not stated

 --

 -- Transit Types

 --

 transit-TypeUnknown BasicVehicleClass ::= 50 -- default type

 transit-TypeOther BasicVehicleClass ::= 51

 transit-BRT BasicVehicleClass ::= 52

 transit-ExpressBus BasicVehicleClass ::= 53

 transit-LocalBus BasicVehicleClass ::= 54

 transit-SchoolBus BasicVehicleClass ::= 55

 transit-FixedGuideway BasicVehicleClass ::= 56

 transit-Paratransit BasicVehicleClass ::= 57

 transit-Paratransit-Ambulance BasicVehicleClass ::= 58

 --

 -- Emergency Vehicle Types

 --

 emergency-TypeUnknown BasicVehicleClass ::= 60 -- default type

 emergency-TypeOther BasicVehicleClass ::= 61 -- includes federal users

 emergency-Fire-Light-Vehicle BasicVehicleClass ::= 62

 emergency-Fire-Heavy-Vehicle BasicVehicleClass ::= 63

 emergency-Fire-Paramedic-Vehicle BasicVehicleClass ::= 64

 emergency-Fire-Ambulance-Vehicle BasicVehicleClass ::= 65

 emergency-Police-Light-Vehicle BasicVehicleClass ::= 66

 emergency-Police-Heavy-Vehicle BasicVehicleClass ::= 67

 emergency-Other-Responder BasicVehicleClass ::= 68

 emergency-Other-Ambulance BasicVehicleClass ::= 69

 --

 -- Other V2X Equipped Travelers

 --

 otherTraveler-TypeUnknown BasicVehicleClass ::= 80 -- default type

 otherTraveler-TypeOther BasicVehicleClass ::= 81

 otherTraveler-Pedestrian BasicVehicleClass ::= 82

 otherTraveler-Visually-Disabled BasicVehicleClass ::= 83

 otherTraveler-Physically-Disabled BasicVehicleClass ::= 84

 otherTraveler-Bicycle BasicVehicleClass ::= 85

 otherTraveler-Vulnerable-Roadworker BasicVehicleClass ::= 86

 --

 -- Other V2X Equipped Device Types

 --

 infrastructure-TypeUnknown BasicVehicleClass ::= 90 -- default type

 infrastructure-Fixed BasicVehicleClass ::= 91

 infrastructure-Movable BasicVehicleClass ::= 92

 equipped-CargoTrailer BasicVehicleClass ::= 93

 BrakeAppliedStatus ::= BIT STRING {

 unavailable (0), -- When set, the brake applied status is unavailable

 leftFront (1), -- Left Front Active

 leftRear (2), -- Left Rear Active

 rightFront (3), -- Right Front Active

 rightRear (4) -- Right Rear Active

 } (SIZE (5))

 BrakeBoostApplied ::= ENUMERATED {

 unavailable (0), -- Vehicle not equipped with brake boost

 -- or brake boost data is unavailable

 off (1), -- Vehicle's brake boost is off

 on (2) -- Vehicle's brake boost is on (applied)

 }

 BrakePedalStatus ::= ENUMERATED {

 unavailable (0), -- Vehicle brake pedal detector is unavailable

 off (1), -- Vehicle's brake pedal is not pressed

 on (2) -- Vehicle's brake pedal is pressed

 }

 CoarseHeading ::= INTEGER (0..240)

 -- Units of 1.5 degrees

 -- over a range of 0\~358.5 degrees

 -- the value 240 shall be used for unavailable

 Confidence ::= INTEGER (0..200)

 -- Units of 0.5 percent

 DDay ::= INTEGER (0..31)

 -- units of days

DescriptiveName ::= IA5String (SIZE(1..63))

 DHour ::= INTEGER (0..31)

 -- units of hours

 DMinute ::= INTEGER (0..60)

 -- units of minutes

 DMonth ::= INTEGER (0..12)

 -- units of months

 DSecond ::= INTEGER (0..65535)

 -- units of milliseconds

 DTimeOffset ::= INTEGER (-840..840)

 -- units of minutes from UTC time

 DYear ::= INTEGER (0..4095)

 -- units of years

 Elevation ::= INTEGER (-4096..61439)

 -- In units of 10 cm steps above or below the reference ellipsoid

 -- Providing a range of -409.5 to + 6143.9 meters

 -- The value -4096 shall be used when Unknown is to be sent

 ElevationConfidence ::= ENUMERATED {

 unavailable (0), -- Not Equipped or unavailable

 elev-500-00 (1), -- (500 m)

 elev-200-00 (2), -- (200 m)

 elev-100-00 (3), -- (100 m)

 elev-050-00 (4), -- (50 m)

 elev-020-00 (5), -- (20 m)

 elev-010-00 (6), -- (10 m)

 elev-005-00 (7), -- (5 m)

 elev-002-00 (8), -- (2 m)

 elev-001-00 (9), -- (1 m)

 elev-000-50 (10), -- (50 cm)

 elev-000-20 (11), -- (20 cm)

 elev-000-10 (12), -- (10 cm)

 elev-000-05 (13), -- (5 cm)

 elev-000-02 (14), -- (2 cm)

 elev-000-01 (15) -- (1 cm)

 }

 EventSource ::= ENUMERATED {

 unknown(0), -- 0 Unknown

 police(1), -- 1 traffic police

 government(2), -- 2 govenment

 meteorological(3), -- 3 meteorological department

 internet(4), -- 4 internet services

 detection(5), -- 5 local detection

 ...

 }

 EventType ::= INTEGER (0..65535)

 -- Traffic event type according to AppendixA and China GB/T 29100-2012

 ExteriorLights ::= BIT STRING {

 -- All lights off is indicated by no bits set

 lowBeamHeadlightsOn (0),

 highBeamHeadlightsOn (1),

 leftTurnSignalOn (2),

 rightTurnSignalOn (3),

 hazardSignalOn (4),

 automaticLightControlOn (5),

 daytimeRunningLightsOn (6),

 fogLightOn (7),

 parkingLightsOn (8)

 } (SIZE (9, ...))

 FuelType ::= INTEGER (0..15)

 unknownFuel FuelType::= 0 -- Gasoline Powered

 gasoline FuelType::= 1

 ethanol FuelType::= 2 -- Including blends

 diesel FuelType::= 3 -- All types

 electric FuelType::= 4

 hybrid FuelType::= 5 -- All types

 hydrogen FuelType::= 6

 natGasLiquid FuelType::= 7 -- Liquefied

 natGasComp FuelType::= 8 -- Compressed

 propane FuelType::= 9

 GNSSstatus ::= BIT STRING {

 unavailable (0), -- Not Equipped or unavailable

 isHealthy (1),

 isMonitored (2),

 baseStationType (3), -- Set to zero if a moving base station,

 -- or if a rover device (an OBU),

 -- set to one if it is a fixed base station

 aPDOPofUnder5 (4), -- A dilution of precision greater than 5

 inViewOfUnder5 (5), -- Less than 5 satellites in view

 localCorrectionsPresent (6), -- pseudo range corrections used

 networkCorrectionsPresent (7) -- RTK type corrections used

 } (SIZE(8))

 Heading ::= INTEGER (0..28800)

 -- Units of 0.0125 degrees

 -- A range of 0 to 359.9875 degrees

 HeadingConfidence ::= ENUMERATED {

 unavailable (0), -- Not Equipped or unavailable

 prec10deg (1), -- 10 degrees

 prec05deg (2), -- 5 degrees

 prec01deg (3), -- 1 degrees

 prec0-1deg (4), -- 0.1 degrees

 prec0-05deg (5), -- 0.05 degrees

 prec0-01deg (6), -- 0.01 degrees

 prec0-0125deg (7) -- 0.0125 degrees

 }

 IntersectionStatusObject ::= BIT STRING {

 manualControlIsEnabled (0),

 -- Timing reported is per programmed values, etc. but person

 -- at cabinet can manually request that certain intervals are

 -- terminated early (e.g. green).

 stopTimeIsActivated (1),

 -- And all counting/timing has stopped.

 failureFlash (2),

 -- Above to be used for any detected hardware failures,

 -- e.g. conflict monitor as well as for police flash

 preemptIsActive (3),

 signalPriorityIsActive (4),

 -- Additional states

 fixedTimeOperation (5),

 -- Schedule of signals is based on time only

 -- (i.e. the state can be calculated)

 trafficDependentOperation (6),

 -- Operation is based on different levels of traffic parameters

 -- (requests, duration of gaps or more complex parameters)

 standbyOperation (7),

 -- Controller: partially switched off or partially amber flashing

 failureMode (8),

 -- Controller has a problem or failure in operation

 off (9),

 -- Controller is switched off

 -- Related to MAP and SPAT bindings

 recentMAPmessageUpdate (10),

 -- Map revision with content changes

 recentChangeInMAPassignedLanesIDsUsed (11),

 -- Change in MAP's assigned lanes used (lane changes)

 -- Changes in the active lane list description

 noValidMAPisAvailableAtThisTime (12),

 -- MAP (and various lanes indexes) not available

 noValidSPATisAvailableAtThisTime (13)

 -- SPAT system is not working at this time

 -- Bits 14,15 reserved at this time and shall be zero

 } (SIZE(16))

 LaneAttributes-Barrier ::= BIT STRING {

 -- With bits as defined:

 median-RevocableLane (0),

 -- this lane may be activated or not based

 -- on the current SPAT message contents

 -- if not asserted, the lane is ALWAYS present

 median (1),

 whiteLineHashing (2),

 stripedLines (3),

 doubleStripedLines (4),

 trafficCones (5),

 constructionBarrier (6),

 trafficChannels (7),

 lowCurbs (8),

 highCurbs (9) -- Bits 10\~15 reserved and set to zero

 } (SIZE (16))

 LaneAttributes-Bike ::= BIT STRING {

 -- With bits as defined:

 bikeRevocableLane (0),

 -- this lane may be activated or not based

 -- on the current SPAT message contents

 -- if not asserted, the lane is ALWAYS present

 pedestrianUseAllowed (1),

 -- The path allows pedestrian traffic,

 -- if not set, this mode is prohibited

 isBikeFlyOverLane (2),

 -- path of lane is not at grade

 fixedCycleTime (3),

 -- the phases use preset times

 -- i.e. there is not a 'push to cross' button

 biDirectionalCycleTimes (4),

 -- ped walk phases use different SignalGroupID

 -- for each direction. The first SignalGroupID

 -- in the first Connection represents 'inbound'

 -- flow (the direction of travel towards the first

 -- node point) while second SignalGroupID in the

 -- next Connection entry represents the 'outbound'

 -- flow. And use of RestrictionClassID entries

 -- in the Connect follow this same pattern in pairs.

 isolatedByBarrier (5),

 unsignalizedSegmentsPresent (6)

 -- The lane path consists of one of more segments

 -- which are not part of a signal group ID

 -- Bits 7\~15 reserved and set to zero

 } (SIZE (16))

 LaneAttributes-Crosswalk ::= BIT STRING {

 -- With bits as defined:

 -- MUTCD provides no suitable \"types\" to use here

 crosswalkRevocableLane (0),

 -- this lane may be activated or not based

 -- on the current SPAT message contents

 -- if not asserted, the lane is ALWAYS present

 bicyleUseAllowed (1),

 -- The path allows bicycle traffic,

 -- if not set, this mode is prohibited

 isXwalkFlyOverLane (2),

 -- path of lane is not at grade

 fixedCycleTime (3),

 -- ped walk phases use preset times

 -- i.e. there is not a 'push to cross' button

 biDirectionalCycleTimes (4),

 -- ped walk phases use different SignalGroupID

 -- for each direction. The first SignalGroupID

 -- in the first Connection represents 'inbound'

 -- flow (the direction of travel towards the first

 -- node point) while second SignalGroupID in the

 -- next Connection entry represents the 'outbound'

 -- flow. And use of RestrictionClassID entries

 -- in the Connect follow this same pattern in pairs.

 hasPushToWalkButton (5),

 -- Has a demand input

 audioSupport (6),

 -- audio crossing cues present

 rfSignalRequestPresent (7),

 -- Supports RF push to walk technologies

 unsignalizedSegmentsPresent (8)

 -- The lane path consists of one of more segments

 -- which are not part of a signal group ID

 -- Bits 9\~15 reserved and set to zero

 } (SIZE (16))

 LaneAttributes-Parking ::= BIT STRING {

 -- With bits as defined:

 -- Parking use details, note that detailed restrictions such as

 -- allowed hours are sent by way of ITIS codes in the TIM message

 parkingRevocableLane (0),

 -- this lane may be activated or not based

 -- on the current SPAT message contents

 -- if not asserted, the lane is ALWAYS present

 parallelParkingInUse (1),

 headInParkingInUse (2),

 doNotParkZone (3),

 -- used to denote fire hydrants as well as

 -- short disruptions in a parking zone

 parkingForBusUse (4),

 parkingForTaxiUse (5),

 noPublicParkingUse (6)

 -- private parking, as in front of

 -- private property

 -- Bits 7\~15 reserved and set to zero

 } (SIZE (16))

 LaneAttributes-Sidewalk ::= BIT STRING { -- With bits as defined:

 sidewalk-RevocableLane (0),

 -- this lane may be activated or not based

 -- on the current SPAT message contents

 -- if not asserted, the lane is ALWAYS present

 bicyleUseAllowed (1),

 -- The path allows bicycle traffic,

 -- if not set, this mode is prohibited

 isSidewalkFlyOverLane (2),

 -- path of lane is not at grade

 walkBikes (3)

 -- bike traffic must dismount and walk

 -- Bits 4\~15 reserved and set to zero

 } (SIZE (16))

 LaneAttributes-Striping ::= BIT STRING {

 -- With bits as defined:

 stripeToConnectingLanesRevocableLane (0),

 -- this lane may be activated or not activated based

 -- on the current SPAT message contents

 -- if not asserted, the lane is ALWAYS present

 stripeDrawOnLeft (1),

 stripeDrawOnRight (2),

 -- which side of lane to mark

 stripeToConnectingLanesLeft (3),

 stripeToConnectingLanesRight (4),

 stripeToConnectingLanesAhead (5)

 -- the stripe type should be

 -- presented to the user visually

 -- to reflect stripes in the

 -- intersection for the type of

 -- movement indicated

 -- Bits 6\~15 reserved and set to zero

 } (SIZE (16))

 LaneAttributes-TrackedVehicle ::= BIT STRING {

 -- With bits as defined:

 spec-RevocableLane (0),

 -- this lane may be activated or not based

 -- on the current SPAT message contents

 -- if not asserted, the lane is ALWAYS present

 spec-commuterRailRoadTrack (1),

 spec-lightRailRoadTrack (2),

 spec-heavyRailRoadTrack (3),

 spec-otherRailType (4) -- Bits 5\~15 reserved and set to zero

 } (SIZE (16))

 LaneAttributes-Vehicle ::= BIT STRING {

 -- With bits as defined:

 isVehicleRevocableLane (0),

 -- this lane may be activated or not based

 -- on the current SPAT message contents

 -- if not asserted, the lane is ALWAYS present

 isVehicleFlyOverLane (1),

 -- path of lane is not at grade

 hovLaneUseOnly (2),

 restrictedToBusUse (3),

 restrictedToTaxiUse (4),

 restrictedFromPublicUse (5),

 hasIRbeaconCoverage (6),

 permissionOnRequest (7) -- e.g. to inform about a lane for e-cars

 } (SIZE (8,...))

 LaneID ::= INTEGER (0..255)

 -- the value 0 shall be used when the lane ID is

 -- not available or not known

 -- the value 255 is reserved for future use

 LaneSharing ::= BIT STRING {

 -- With bits as defined:

 overlappingLaneDescriptionProvided (0),

 -- Assert when another lane object is present to describe the

 -- path of the overlapping shared lane

 -- this construct is not used for lane objects which simply cross

 multipleLanesTreatedAsOneLane (1),

 -- Assert if the lane object path and width details represents

 -- multiple lanes within it that are not further described

 -- Various modes and type of traffic that may share this lane:

 otherNonMotorizedTrafficTypes (2), -- horse drawn etc.

 individualMotorizedVehicleTraffic (3),

 busVehicleTraffic (4),

 taxiVehicleTraffic (5),

 pedestriansTraffic (6),

 cyclistVehicleTraffic (7),

 trackedVehicleTraffic (8),

 pedestrianTraffic (9)

 } (SIZE (10))

 -- All zeros would indicate 'not shared' and 'not overlapping'

 LaneWidth ::= INTEGER (0..32767)

 -- units of 1 cm

 Latitude ::= INTEGER (-900000000..900000001)

 -- Units of 1/10 micro degree

 -- Providing a range of plus-minus 90 degrees

 LightbarInUse ::= ENUMERATED {

 unavailable (0), -- Not Equipped or unavailable

 notInUse (1), -- none active

 inUse (2),

 yellowCautionLights (3),

 schooldBusLights (4),

 arrowSignsActive (5),

 slowMovingVehicle (6),

 freqStops (7)

 }

 LightState ::= ENUMERATED {

 unavailable (0),

 -- This state is used for unknown or error

 dark (1),

 -- The signal is dark (unlit)

 -- Reds

 flashing-red (2),

 -- Reserved for special scenarios

 red (3),

 -- Driver Action:

 -- Stop vehicle at stop line.

 -- Do not proceed.

 -- Greens

 flashing-green (4),

 -- Reserved for special scenarios

 permissive-green (5),

 -- Driver Action:

 -- Proceed with caution,

 -- must yield to all conflicting traffic

 -- Conflicting traffic may be present

 -- in the intersection conflict area

 protected-green (6),

 -- Driver Action:

 -- Proceed, tossing caution to the wind,

 -- in indicated (allowed) direction.

 -- Yellows / Ambers

 -- The vehicle is not allowed to cross the stop bar if it is possible

 -- to stop without danger.

 yellow (7),

 -- Driver Action:

 -- Prepare to stop.

 -- Proceed if unable to stop,

 -- in indicated direction (to connected lane)

 -- Clear Intersection.

 flashing-yellow (8) ,

 -- Driver Action:

 -- Proceed with caution,

 -- Conflicting traffic may be present

 -- in the intersection conflict area

 ...

 }

 Longitude ::= INTEGER (-1799999999..1800000001)

 -- Units of 1/10 micro degree

 -- Providing a range of plus-minus 180 degrees

 MinuteOfTheYear ::= INTEGER (0..527040)

 -- the value 527040 shall be used for invalid

MsgCount ::= INTEGER (0..127)

 NodeID ::= INTEGER (0..65535)

 -- The values zero through 255 are allocated for testing purposes

 -- Note that the value assigned to a node will be

 -- unique within a given regional ID only

 OffsetLL-B12 ::= INTEGER (-2048..2047)

 -- A range of +- 0.0002047 degrees

 -- Units of 0.1 microdegrees

 OffsetLL-B14 ::= INTEGER (-8192..8191)

 -- A range of +- 0.0008191 degrees

 -- Units of 0.1 microdegrees

 OffsetLL-B16 ::= INTEGER (-32768..32767)

 -- A range of +- 0.0032767 degrees

 -- Units of 0.1 microdegrees

 OffsetLL-B18 ::= INTEGER (-131072..131071)

 -- A range of +- 0.0131071 degrees

 -- Units of 0.1 microdegrees

 OffsetLL-B22 ::= INTEGER (-2097152..2097151)

 -- A range of +- 0.2097151 degrees

 -- Units of 0.1 microdegrees

 OffsetLL-B24 ::= INTEGER (-8388608..8388607)

 -- A range of +- 0.8388607 degrees

 -- Units of 0.1 microdegrees

 ParticipantType ::= ENUMERATED {

 unknown (0), -- Unknown

 motor (1), -- motor

 non-motor (2), -- non-motor

 pedestrian (3), -- pedestrian

 rsu (4), -- rsu

 ...

 }

 PhaseID ::= INTEGER (0..255)

 -- The value 0 shall be used when the ID is not available or not known

 PositionConfidence ::= ENUMERATED {

 unavailable (0), -- Not Equipped or unavailable

 a500m (1), -- 500m or about 5 * 10 \^ -3 decimal degrees

 a200m (2), -- 200m or about 2 * 10 \^ -3 decimal degrees

 a100m (3), -- 100m or about 1 * 10 \^ -3 decimal degrees

 a50m (4), -- 50m or about 5 * 10 \^ -4 decimal degrees

 a20m (5), -- 20m or about 2 * 10 \^ -4 decimal degrees

 a10m (6), -- 10m or about 1 * 10 \^ -4 decimal degrees

 a5m (7), -- 5m or about 5 * 10 \^ -5 decimal degrees

 a2m (8), -- 2m or about 2 * 10 \^ -5 decimal degrees

 a1m (9), -- 1m or about 1 * 10 \^ -5 decimal degrees

 a50cm (10), -- 0.50m or about 5 * 10 \^ -6 decimal degrees

 a20cm (11), -- 0.20m or about 2 * 10 \^ -6 decimal degrees

 a10cm (12), -- 0.10m or about 1 * 10 \^ -6 decimal degrees

 a5cm (13), -- 0.05m or about 5 * 10 \^ -7 decimal degrees

 a2cm (14), -- 0.02m or about 2 * 10 \^ -7 decimal degrees

 a1cm (15) -- 0.01m or about 1 * 10 \^ -7 decimal degrees

 }

 Radius ::= INTEGER (0..65535)

 -- Define radius

 -- Unit is 0.1m

 RadiusOfCurvature ::= INTEGER (-32767..32767)

 -- Units of 10cm

 -- A straight path to use value of 32767

 ReferenceLanes ::= BIT STRING {

 -- With bits as defined:

 reserved(0),

 lane1(1),

 lane2(2),

 lane3(3),

 lane4(4),

 lane5(5),

 lane6(6),

 lane7(7),

 lane8(8),

 lane9(9),

 lane10(10),

 lane11(11),

 lane12(12),

 lane13(13),

 lane14(14),

 lane15(15)

 } (SIZE (16))

 -- Set bit to 1 if the related lane is effective

 -- Support maximum 15 lanes

 ResponseType ::= ENUMERATED {

 notInUseOrNotEquipped (0),

 emergency (1), -- active service call at emergency level

 nonEmergency (2), -- also used when returning from service call

 pursuit (3), -- sender driving may be erratic

 stationary (4), -- sender is not moving, stopped along roadside

 slowMoving (5), -- such as a litter trucks, etc.

 stopAndGoMovement (6), -- such as school bus or garbage truck

 ...

 }

 RSIPriority ::= OCTET STRING (SIZE(1))

 -- The lower five bits are reserved and shall be set to zero

 -- Value from B00000000 to B11100000 represents the lowest to the highest level

 RoadRegulatorID ::= INTEGER (0..65535)

 -- The value zero shall be used for testing only

 SemiMajorAxisAccuracy ::= INTEGER (0..255)

 -- semi-major axis accuracy at one standard dev

 -- range 0-12.7 meter, units of 0.05m

 -- 254 = any value equal or greater than 12.70 meter

 -- 255 = unavailable semi-major axis value

 SemiMajorAxisOrientation ::= INTEGER (0..65535)

 -- orientation of semi-major axis

 -- relative to true north (0\~359.9945078786 degrees)

 -- Units of 360/65535 deg = 0.0054932479

 -- a value of 0 shall be 0 degrees

 -- a value of 1 shall be 0.0054932479 degrees

 -- a value of 65534 shall be 359.9945078786 deg

 -- a value of 65535 shall be used for orientation unavailable

 SemiMinorAxisAccuracy ::= INTEGER (0..255)

 -- semi-minor axis accuracy at one standard dev

 -- range 0-12.7 meter, units of 0.05m

 -- 254 = any value equal or greater than 12.70 meter

 -- 255 = unavailable semi-minor axis value

 SignType ::= INTEGER (0..65535)

 -- Value 0 means unknown type or using text description

 -- Traffic sign types refer to China GB 5768.2-2009

 SirenInUse ::= ENUMERATED {

 unavailable (0), -- Not Equipped or unavailable

 notInUse (1),

 inUse (2),

 reserved (3) -- for future use

 }

 SourceType ::= ENUMERATED {

 unknown(0),

 selfinfo(1),

 v2x(2),

 video(3),

 microwaveRadar(4),

 loop(5),

 lidar(6),

 integrated(7),

 ...

 }

 Speed ::= INTEGER (0..8191)

 -- Units of 0.02 m/s

 -- The value 8191 indicates that

 -- speed is unavailable

 SpeedConfidence ::= ENUMERATED {

 unavailable (0), -- Not Equipped or unavailable

 prec100ms (1), -- 100 meters / sec

 prec10ms (2), -- 10 meters / sec

 prec5ms (3), -- 5 meters / sec

 prec1ms (4), -- 1 meters / sec

 prec0-1ms (5), -- 0.1 meters / sec

 prec0-05ms (6), -- 0.05 meters / sec

 prec0-01ms (7) -- 0.01 meters / sec

 }

 SpeedLimitType ::= ENUMERATED {

 unknown, -- Speed limit type not available

 maxSpeedInSchoolZone, -- Only sent when the limit is active

 maxSpeedInSchoolZoneWhenChildrenArePresent, -- Sent at any time

 maxSpeedInConstructionZone, -- Used for work zones, incident zones, etc.

 -- where a reduced speed is present

 vehicleMinSpeed,

 vehicleMaxSpeed, -- Regulatory speed limit for general traffic

 vehicleNightMaxSpeed,

 truckMinSpeed,

 truckMaxSpeed,

 truckNightMaxSpeed,

 vehiclesWithTrailersMinSpeed,

 vehiclesWithTrailersMaxSpeed,

 vehiclesWithTrailersNightMaxSpeed,

 ...

 }

 StabilityControlStatus ::= ENUMERATED {

 unavailable (0), -- Not Equipped with SC

 -- or SC status is unavailable

 off (1), -- Off

 on (2), -- On or active (but not engaged)

 engaged (3) -- stability control is Engaged

 }

 SteeringWheelAngle ::= INTEGER (-126..127)

 -- Units of 1.5 degrees, a range of -189 to +189 degrees

 -- +001 = +1.5 deg

 -- -126 = -189 deg and beyond

 -- +126 = +189 deg and beyond

 -- +127 to be used for unavailable

 SteeringWheelAngleConfidence ::= ENUMERATED {

 unavailable (0), -- Not Equipped with Wheel angle

 -- or Wheel angle status is unavailable

 prec2deg (1), -- 2 degrees

 prec1deg (2), -- 1 degree

 prec0-02deg (3) -- 0.02 degrees

 }

 TimeConfidence ::= ENUMERATED {

 unavailable (0), -- Not Equipped or unavailable

 time-100-000 (1), -- Better than 100 Seconds

 time-050-000 (2), -- Better than 50 Seconds

 time-020-000 (3), -- Better than 20 Seconds

 time-010-000 (4), -- Better than 10 Seconds

 time-002-000 (5), -- Better than 2 Seconds

 time-001-000 (6), -- Better than 1 Second

 time-000-500 (7), -- Better than 0.5 Seconds

 time-000-200 (8), -- Better than 0.2 Seconds

 time-000-100 (9), -- Better than 0.1 Seconds

 time-000-050 (10), -- Better than 0.05 Seconds

 time-000-020 (11), -- Better than 0.02 Seconds

 time-000-010 (12), -- Better than 0.01 Seconds

 time-000-005 (13), -- Better than 0.005 Seconds

 time-000-002 (14), -- Better than 0.002 Seconds

 time-000-001 (15), -- Better than 0.001 Seconds

 -- Better than one millisecond

 time-000-000-5 (16), -- Better than 0.000,5 Seconds

 time-000-000-2 (17), -- Better than 0.000,2 Seconds

 time-000-000-1 (18), -- Better than 0.000,1 Seconds

 time-000-000-05 (19), -- Better than 0.000,05 Seconds

 time-000-000-02 (20), -- Better than 0.000,02 Seconds

 time-000-000-01 (21), -- Better than 0.000,01 Seconds

 time-000-000-005 (22), -- Better than 0.000,005 Seconds

 time-000-000-002 (23), -- Better than 0.000,002 Seconds

 time-000-000-001 (24), -- Better than 0.000,001 Seconds

 -- Better than one micro second

 time-000-000-000-5 (25), -- Better than 0.000,000,5 Seconds

 time-000-000-000-2 (26), -- Better than 0.000,000,2 Seconds

 time-000-000-000-1 (27), -- Better than 0.000,000,1 Seconds

 time-000-000-000-05 (28), -- Better than 0.000,000,05 Seconds

 time-000-000-000-02 (29), -- Better than 0.000,000,02 Seconds

 time-000-000-000-01 (30), -- Better than 0.000,000,01 Seconds

 time-000-000-000-005 (31), -- Better than 0.000,000,005 Seconds

 time-000-000-000-002 (32), -- Better than 0.000,000,002 Seconds

 time-000-000-000-001 (33), -- Better than 0.000,000,001 Seconds

 -- Better than one nano second

 time-000-000-000-000-5 (34), -- Better than 0.000,000,000,5 Seconds

 time-000-000-000-000-2 (35), -- Better than 0.000,000,000,2 Seconds

 time-000-000-000-000-1 (36), -- Better than 0.000,000,000,1 Seconds

 time-000-000-000-000-05 (37), -- Better than 0.000,000,000,05 Seconds

 time-000-000-000-000-02 (38), -- Better than 0.000,000,000,02 Seconds

 time-000-000-000-000-01 (39) -- Better than 0.000,000,000,01 Seconds

 }

 TimeMark ::= INTEGER (0..36001)

 -- Tenths of a second in the current or next hour

 -- In units of 1/10th second from UTC time

 -- A range of 0\~36000 covers one hour

 -- The values 35991..35999 are used when a leap second occurs

 -- The value 36000 is used to indicate time >3600 seconds

 -- 36001 is to be used when value undefined or unknown

 -- Note that this is NOT expressed in GNSS time

 -- or in local time

 TimeOffset ::= INTEGER (1..65535)

 -- Units of 10 mSec,

 -- with a range of 0.01 seconds to 10 minutes and 55.34 seconds

 -- a value of 65534 to be used for 655.34 seconds or greater

 -- a value of 65535 to be unavailable

 TractionControlStatus ::= ENUMERATED {

 unavailable (0), -- Not Equipped with traction control

 -- or traction control status is unavailable

 off (1), -- traction control is Off

 on (2), -- traction control is On (but not Engaged)

 engaged (3) -- traction control is Engaged

 }

 TransmissionState ::= ENUMERATED {

 neutral (0), -- Neutral

 park (1), -- Park

 forwardGears (2), -- Forward gears

 reverseGears (3), -- Reverse gears

 reserved1 (4),

 reserved2 (5),

 reserved3 (6),

 unavailable (7)-- not-equipped or unavailable value

 -- Any related speed is relative to the vehicle reference frame used

 }

 VehicleEventFlags ::= BIT STRING {

 eventHazardLights (0),

 eventStopLineViolation (1), -- Intersection Violation

 eventABSactivated (2),

 eventTractionControlLoss (3),

 eventStabilityControlactivated (4),

 eventHazardousMaterials (5),

 eventReserved1 (6),

 eventHardBraking (7),

 eventLightsChanged (8),

 eventWipersChanged (9),

 eventFlatTire (10),

 eventDisabledVehicle (11), -- The DisabledVehicle DF may also be sent

 eventAirBagDeployment (12)

 } (SIZE (13, ...))

 VehicleHeight ::= INTEGER (0..127)

 -- Units of 5 cm, range to 6.35 meters

 VehicleLength ::= INTEGER (0.. 4095)

 -- Units of 1 cm with a range of >40 meters

 VehicleWidth ::= INTEGER (0..1023)

 -- Units are 1 cm with a range of >10 meters

 VerticalAcceleration ::= INTEGER (-127..127)

 -- Units of 0.02 G steps over -2.52 to +2.54 G

 -- The value +127 shall be used for ranges >= 2.54 G

 -- The value -126 shall be used for ranges <= 2.52 G

 -- The value -127 shall be used for unavailable

 VertOffset-B07 ::= INTEGER (-64..63)

 -- Units of 10 cm

 -- with a range of +- 6.3 meters vertical

 -- value 63 to be used for 63 or greater

 -- value -63 to be used for -63 or greater

 -- value -64 to be unavailable

 VertOffset-B08 ::= INTEGER (-128..127)

 -- Units of 10 cm

 -- with a range of +- 12.7 meters vertical

 -- value 127 to be used for 127 or greater

 -- value -127 to be used for -127 or greater

 -- value -128 to be unavailable

 VertOffset-B09 ::= INTEGER (-256..255)

 -- Units of 10 cm

 -- with a range of +- 25.5 meters vertical

 -- value 255 to be used for 255 or greater

 -- value -255 to be used for -255 or greater

 -- value -256 to be unavailable

 VertOffset-B10 ::= INTEGER (-512..511)

 -- Units of 10 cm

 -- with a range of +- 51.1 meters vertical

 -- value 511 to be used for 511 or greater

 -- value -511 to be used for -511 or greater

 -- value -512 to be unavailable

 VertOffset-B11 ::= INTEGER (-1024..1023)

 -- Units of 10 cm

 -- with a range of +- 102.3 meters vertical

 -- value 1023 to be used for 1023 or greater

 -- value -1023 to be used for -1023 or greater

 -- value -1024 to be unavailable

 VertOffset-B12 ::= INTEGER (-2048..2047)

 -- Units of 10 cm

 -- with a range of +- 204.7 meters vertical

 -- value 2047 to be used for 2047 or greater

 -- value -2047 to be used for -2047 or greater

 -- value -2048 to be unavailable

 YawRate ::= INTEGER (-32767..32767)

 -- Units of 0.01 degrees per second (signed)
END
